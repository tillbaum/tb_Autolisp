;TOTALTX - Adds text entities.
;
;Jeffery P Sanders
;
(defun C:TTX(/ sum eset enlist oldht len ln total pt)
 (princ "\n \n \nSelect dText: ")
 (if (setq eset (ssget))
  (progn
   (setq len(sslength eset) ln(- len 1) total 0)
   (while(>=(setq len(- len 1))0)
    (setq en(ssname eset len)enlist(entget en))
    (if(= "TEXT" (cdr (assoc 0 enlist)))
     (progn
      (if (= len ln)
	(princ "\n \n \n...Please Wait....Totaling Selection Set...")
      )
      (setq sum(atof(cdr(assoc 1 enlist))))
      (setq total(+ total sum))
     )(setq ln(- ln 1))
   ))
   (princ "\n \nTotal = ")(princ total)
   (setq pt(getpoint "\nInsertion Point:"))
   
   (command "text" pt "0" total))
   (princ "\n....TTX.lsp Complete. \n ")
  )
 (princ "\n \n....*ERROR*.. Nothing Selected! \n ")
 )
 (princ)
)
