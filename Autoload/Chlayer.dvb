Attribute VB_Name = "Module1"
Sub chlayer()
'name of function

    UserForm1.Show
    'display the dialogue box
    'UserForm1
    
End Sub

Attribute VB_Name = "UserForm1"
Attribute VB_Base = "0{9956019D-77A6-4136-B6D7-2DE46E777C20}{6B366EB5-11B2-47B3-BFBC-56C1567487D8}"
Attribute VB_GlobalNameSpace = False
Attribute VB_Creatable = False
Attribute VB_PredeclaredId = True
Attribute VB_Exposed = False
Attribute VB_TemplateDerived = False
Attribute VB_Customizable = False
Private Sub CommandButton1_Click()

Dim Entity As Object
'declare variable as local

Me.Hide
'hide the dialogue box

Set ss = ThisDrawing.SelectionSets.Add("NEWSS")
'create a selection set reference

ss.SelectOnScreen
'select the objects to change

For Each Entity In ss
'for every entity in the selection set

    Entity.Layer = ListBox1.Text
    'change the layer to the layer name
    'selected in the list box
    
Next
'process the next entity

End
'end the programme

End Sub

Private Sub CommandButton2_Click()

    End
    'end the programme
    
End Sub

Private Sub UserForm_Click()

End Sub

Private Sub UserForm_Initialize()
Dim AllLayers As Object
Dim Layer As Object
'declare local variables


Set AllLayers = ThisDrawing.Layers
'get the layers from the layers collection

For Each Layer In AllLayers
'for every layer listed

    ListBox1.AddItem Layer.Name
    'add the layer name to the list box
    
    Next
    'carry on looping
    
End Sub
